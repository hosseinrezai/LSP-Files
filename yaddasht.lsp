(defun c:yaddasht()  
  (princ "Version:1.2(1401/11/20-2023/02/09)")
  (setq cen (getvar 'viewctr))
  (initget "New Continue")
  (setq ans (cond ((getkword "\nChoose [New setting/Continue last setting] <Continue last setting>: ")) ("Continue")))
  (if (= ans "New") 
    (progn 
      (setq gamx (getdist "\nDX:"))
      (setq gamy (getdist "\nDY:"))
      (setq a (seting))
      (setq saveaddress (nth 0 a))
      (setq lis (nth 1 a))
    )
  )
  
  (while (setq data (getdata lis))
    (setq cen (list (+ (nth 0 cen) gamx) (+ (nth 1 cen) gamy)))
    (setq fil (open saveaddress "A"))
    (setq count 0)
    (setq str "")
    (while (< count (length data))
      (setq str (strcat str "	" (nth count data)))
      (setq count (+ count 1))
    )    
    (WRITE-LINE str fil)
    (close fil)
  )
)
;;--------------------------------------------------------------------------------------------------------------------------------------- seting
(defun seting()  
  (setq settinglist (list))
  (princ "\n")  
  (setq saveaddress "D:\\yaddasht.txt")
  (setq a (getstring (strcat "\n enter file name (current name is:" saveaddress "):")))
  (if (= a "")
    (princ)
    (setq saveaddress  a)
  )
  (initget "Text Point Distance Area Finish")
    (setq a (cond ((getkword "\nChoose [Text / Point / Distance / Area / Finish] <Finish>: ")) ("Finish")))
  (while (/= a "Finish")
    (setq st (getstring (strcat "\n" a " Description:")))
    (setq p (getpoint (strcat "\nwhere is " st "? click on it:")))
    (setq settinglist (append settinglist (list (list a st (- (nth 0 p) (nth 0 cen)) (- (nth 1 p) (nth 1 cen))))));; (function description x y value)    
    (initget "Text Point Distance Area Finish")
    (setq a (cond ((getkword "\nChoose [Text / Point / Distance / Area / Finish] <Finish>: ")) ("Finish")))
  ) 
  (setq count 0)
  (setq fil (open saveaddress "A"))
  (setq count 0)
  (setq str "")
  (while (< count (length settinglist))
    (setq str (strcat str "	" (nth  1 (nth count settinglist))))
    (setq count (+ count 1))
  )
  (WRITE-LINE str fil)
  (close fil)
  (princ (list saveaddress settinglist))
)
;;--------------------------------------------------------------------------------------------------------------------------------------- getdata
(defun getdata(tanzim)
    (setq count 0)
    (setq dat (list))   
    (while (< count (length tanzim))
      (progn
        (command "_.ZOOM" "c"
                 (list (+ (nth 0 cen) (nth 2 (nth count tanzim))) (+ (nth 1 cen) (nth 3 (nth count tanzim))))
                 (getvar 'viewsize)
        )        
        (if (= "Text" (nth 0 (nth count tanzim)))
          (setq dat (append  dat (list (getext tanzim count))))
          (if (= "Point" (nth 0 (nth count tanzim)))
            (setq dat (append  dat (list (getpt tanzim count))))
            (if (= "Distance" (nth 0 (nth count tanzim)))
              (setq dat (append  dat (list (getdistance tanzim count))))
              (if (= "Area" (nth 0 (nth count tanzim)))
              (setq dat (append  dat (list (getvol tanzim count))))
              )
            )
          )
        )
      )
      (setq count (+ count 1))
    )
  (princ dat)  
)
;;--------------------------------------------------------------------------------------------------------------------------------------- getext
(defun getext(tanzim1 count1)
  (cdr (assoc 1 (entget (car (nentsel (strcat "\n" (nth 1 (nth count1 tanzim1)) ":"))))))
)
;;--------------------------------------------------------------------------------------------------------------------------------------- getpont
(defun getpt(tanzim1 count1)
  (setq p (getpoint (strcat "\n" (nth 1 (nth count1 tanzim1)) ":")))
  (princ (strcat "(x=" (rtos (nth 0 p) 2 2) ", y=" (rtos (nth 1 p) 2 2) ", z=" (rtos (nth 2 p) 2 2) ")")  )
)
;;--------------------------------------------------------------------------------------------------------------------------------------- getdistance

(defun getdistance(tanzim1 count1)
  (setq i 1)
  (setq lent 0)  
  (setvar 'OSMODE 33)
  (if (setq p1 (getpoint (strcat "\n" (nth 1 (nth count1 tanzim1)) (rtos i 2 0) ":")))
    (progn
      (setq i (+ i 1))
      (command "_.CIRCLE" (list 0 0) "0.05")
      (while (setq p2 (getpoint (strcat "\n" (nth 1 (nth count1 tanzim1)) (rtos i 2 0) ":")))
	      (setq lent (+ lent (distance p1 p2)))
	      (setq p1 p2)
	      (setq i (+ i 1))
	      (setvar 'OSMODE 0)
	      (command "_.ERASE" "l" "")
	      (command "_.CIRCLE" p1 "0.05")
	      (setvar 'OSMODE 1)
      )
      (command "_.ERASE" "l" "")
    )
  )
  (princ (rtos lent 2 2)) 
)
;;--------------------------------------------------------------------------------------------------------------------------------------- getvol
(defun getvol(tanzim1 count1) 
  (setq v 0)
  (while (setq p (getpoint (strcat "\n" (nth 1 (nth count1 tanzim1)) "(" (rtos v) "):")))
    (command "bpoly" p "")
    (command "area" "o" "l")
    (setq av (getvar "area"))
    (setq v (+ v av))
  )
  (princ (rtos v 2 2))
)
