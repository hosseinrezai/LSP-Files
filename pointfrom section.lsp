(defun c:point_from_section ( / theobj thelist n xval yval fname fn)
  (vl-load-com)
  (setq gamx 64.45)
  (setq gamy -14)
  (setq zom 30)
  (setq cen (getpoint "\n markaz:"))
  (setvar 'OSMODE 1)
  (command "._zoom" "c" cen zom)
  (setq j 1)
  (setq jj 1)
  (while (setq bkm (cdr (assoc 1 (entget (car (nentsel "\n B-KM:"))))))
    	;(setq skm (cdr (assoc 1 (entget (car (nentsel "\n S-KM:"))))))
    	(setq datumcode (cdr (assoc 1 (entget (car (nentsel "\n datum code:"))))))
    	(setq datumpoint (getpoint "\n datum point:"))
    	
    
	(setq theobj (car (entsel "\nSelect a Polyline: ")))
	(setq theobj (vlax-ename->vla-object theobj))
	(if (= (vlax-get-property theobj 'ObjectName) "AcDbPolyline")
		(progn
			(setq thelist (vlax-get-property theobj 'coordinates))
			(setq thelist (vlax-safearray->list  (variant-value thelist)))
			(setq n 0)
		  	(repeat (/ (length thelist) 2)
				(setq xval (rtos (nth n thelist)))
				(setq n (1+ n))
				(setq yval (rtos (nth n thelist)))e
				(setq strpoint  (strcat bkm "	" datumcode "	" (rtos (nth 0 datumpoint)) "," (rtos (nth 1 datumpoint)) "	" xval "," yval "	"))
			  	(setq fname "d:\\coord.txt")
			  	(setq fn (open fname "A"))
			  	(write-line  strpoint  fn)
				(close fn)
				(setq n (1+ n))
				)
			)
		(alert "This is not a Polyline! - Please try again.")
		)
	(princ)
	(setq cen (list (nth 0 cen) (+ (nth 1 cen) gamy)))
		(if (= jj 2004)
	    		(progn
		  		(setq cen (list (- (nth 0 cen) (* gamx (/ jj 2))) (+ (nth 1 cen) (* gamy 2))))
		  		(setq jj 0)
		  		)
	    		)
	    	(if (= j 2)
	      		(progn
				(setq cen (list (+ (nth 0 cen) gamx) (- (nth 1 cen) (* gamy j))))
				(setq j 0)
				)
		  	)
		(setq j (+ j 1))
	    	(setq jj (+ jj 1))
	    	(command "._zoom" "c" cen zom)
    		)
    )
(princ)
